// From: https://network.developer.nokia.com/sr/learn/yang/understanding-yang/

// Below is a .yang file of just definitions, to be imported into below or other modules as needed

module engineer_types {
    yang-version 1.1;
    namespace "urn:nokia.com:srexperts:types"; // Header: Uniquely identify each module on a system implementing NETCONF
    prefix "types"; // Header: A short notation for the module for easy reference
    organization "Zane Co."
    revision 2019-05-06; // Header: Allows a user to differentiate different versions of the data model
    typedef age_type {
        description "Engineers start work at 18 and should be retired by 110";
        type int8 {
            range "18 .. 110";
        }
        units years;
    }
    typedef transportation_type {
        description "Method of transportation";
        type enumeration {
            enum foot;
            enum bicycle;
            enum car;
            enum bus;
            enum train;
            enum boat;
            enum aeroplane;
        }
    }
}


// Below would be in a seperate .yang file
module engineer {
    yang-version 1.1;
    namespace "urn:nokia.com:srexperts:engineer";
    prefix "engineer";
    import engineer_types { // This imports the first module above, where we created custom data types - NOTE: imports follow the header statements!
      prefix "types";
    }
    revision 2019-05-06;
    container engineer {
        description "Its me";
        leaf name {
            mandatory true;
            type string;
        }
        leaf age {
            type types:age_type;
        }
        leaf commute {
            type types:transportation_type;
        }
    }
}
